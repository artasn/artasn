External-X690 DEFINITIONS EXPLICIT TAGS ::= BEGIN

-- This is how the EXTERNAL type is encoded in the presentation layer.
-- This is to ensure backwards compatability between the X.208 and X.680
-- implementations of the EXTERNAL type.
-- See X.690 clause 8.18 and its subclauses to see how the X.680 EXTERNAL type is mapped to this type.
-- The X.208 EXTERNAL type is directly equivalent to this type at the presentation layer.

-- This module is not actually loaded as part of the the standard library,
-- but instead serves as reference material for the `ber_encode_external` function in src/encoding/ber/encode.rs.

-- EXTERNAL
External ::= [UNIVERSAL 8] IMPLICIT SEQUENCE {
    direct-reference      OBJECT IDENTIFIER OPTIONAL,
    indirect-reference    INTEGER           OPTIONAL,
    data-value-descriptor ObjectDescriptor  OPTIONAL,
    encoding CHOICE {
        single-ASN1-type [0] ABSTRACT-SYNTAX.&Type,
        octet-aligned    [1] IMPLICIT OCTET STRING,
        arbitrary        [2] IMPLICIT BIT STRING
    }
}

END
