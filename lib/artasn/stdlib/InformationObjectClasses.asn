InformationObjectClasses DEFINITIONS EXPLICIT TAGS ::= BEGIN

-- TYPE-IDENTIFIER
CLASS-TYPE-IDENTIFIER ::= CLASS {
    &id OBJECT IDENTIFIER UNIQUE,
    &Type
} WITH SYNTAX {
    &Type IDENTIFIED BY &id
}

-- ABSTRACT-SYNTAX
CLASS-ABSTRACT-SYNTAX ::= CLASS {
   &id OBJECT IDENTIFIER UNIQUE,
   &Type,
   &property BIT STRING { handles-invalid-encodings(0) } DEFAULT {}
} WITH SYNTAX {
   &Type IDENTIFIED BY &id [HAS PROPERTY &property]
}

-- INSTANCE OF CLASS-TYPE
InstanceOf{CLASS-TYPE} ::= [UNIVERSAL 8] IMPLICIT SEQUENCE {
    type-id   CLASS-TYPE.&id,
    value [0] CLASS-TYPE.&Type
}

-- INSTANCE OF CLASS-TYPE ({ClassTypeSet})
ConstrainedInstanceOf{CLASS-TYPE, CLASS-TYPE:ClassTypeSet} ::= [UNIVERSAL 8] IMPLICIT SEQUENCE {
    type-id   CLASS-TYPE.&id   ({ClassTypeSet}),
    value [0] CLASS-TYPE.&Type ({ClassTypeSet}{@type-id})
}

END
