UniversalTypeTest DEFINITIONS IMPLICIT TAGS ::= BEGIN

EnumeratedType ::= ENUMERATED {
    foo (0),
    bar (1),
    baz (2)
}

BasicSequenceType ::= SEQUENCE {
    foo INTEGER OPTIONAL,
    bar OCTET STRING,
    baz BOOLEAN DEFAULT TRUE
}

BasicSetType ::= SET {
    foo INTEGER OPTIONAL,
    bar OCTET STRING,
    baz BOOLEAN DEFAULT TRUE
}

BasicChoice ::= CHOICE {
    foo INTEGER,
    bar BOOLEAN
}

SequenceType ::= SEQUENCE {
    boolean BOOLEAN,
    integer INTEGER,
    bitString BIT STRING,
    octetString OCTET STRING,
    null NULL,
    objectIdentifier OBJECT IDENTIFIER,
    objectDescriptor ObjectDescriptor,
    external EXTERNAL,
    real REAL,
    enumerated EnumeratedType,
    embeddedPDV EMBEDDED PDV,
    utf8String UTF8String,
    choice BasicChoice,
    relativeOID RELATIVE-OID,
    time TIME,
    sequence BasicSequenceType,
    set BasicSetType,
    numericString NumericString,
    printableString PrintableString,
    teletexString TeletexString,
    videotexString VideotexString,
    ia5String IA5String,
    utcTime UTCTime,
    generalizedTime GeneralizedTime,
    graphicString GraphicString,
    visibleString VisibleString,
    generalString GeneralString,
    universalString UniversalString,
    characterString CHARACTER STRING,
    bmpString BMPString,
    date DATE,
    timeOfDay TIME-OF-DAY,
    dateTime DATE-TIME,
    duration DURATION
}

sequenceValue SequenceType ::= {
    boolean TRUE,
    integer 1337,
    bitString '01000101'B,
    octetString 'DEADBEEF'H,
    null NULL,
    objectIdentifier { joint-iso-itu-t artasn(1337) test(47) oid(81) },
    objectDescriptor "ObjectDescriptor",
    external {
        identification syntax : { joint-iso-itu-t artasn(1337) test(47) external-syntax(82) },
        data-value '1337'H
    },
    real { mantissa 1, base 2, exponent -1 },
    enumerated baz,
    embeddedPDV {
        identification syntax : { joint-iso-itu-t artasn(1337) test(47) embedded-pdv-syntax(83) },
        data-value '1337'H
    },
    utf8String "UTF8String",
    choice foo : 7331,
    relativeOID { artasn(1337) foo(1) bar(2) baz(3) },
    time "2025-03-09T16:21:05-08:00",
    sequence {
        foo 1,
        bar '0123456789ABCDEF'H,
        baz FALSE
    },
    set {
        bar 'F0F1F2F3F4F5F6F7'H
    },
    numericString "01234 56789",
    printableString "PrintableString",
    teletexString "TeletexString",
    videotexString "VideotexString",
    ia5String "IA5String",
    utcTime "250309162105Z",
    generalizedTime "20250309162105.123Z",
    graphicString "GraphicString",
    visibleString "VisibleString",
    generalString "GeneralString",
    universalString "UniversalString",
    characterString {
        identification syntax : { joint-iso-itu-t artasn(1337) test(47) character-string-syntax(83) },
        string-value '1337'H
    },
    bmpString "BMPString",
    date "2025-03-09",
    timeOfDay "16:21:05",
    dateTime "2025-03-09T16:21:05",
    duration "P2Y10M15DT10H20M30S"
}

END
