PerBitStringTest DEFINITIONS IMPLICIT TAGS ::= BEGIN

UnconstrainedBitString ::= BIT STRING
ubs-1 UnconstrainedBitString ::= ''B
ubs-2 UnconstrainedBitString ::= ''H
ubs-3 UnconstrainedBitString ::= '00'H
ubs-4 UnconstrainedBitString ::= '1337'H
ubs-5 UnconstrainedBitString ::= '1'B
ubs-6 UnconstrainedBitString ::= '0'B
ubs-7 UnconstrainedBitString ::= '1010'B
ubs-8 UnconstrainedBitString ::= '10101010'B
ubs-9 UnconstrainedBitString ::= '101010101'B

UnconstrainedBitStringList ::= SEQUENCE OF BIT STRING
ubsl UnconstrainedBitStringList ::= { ubs-1, ubs-2, ubs-3, ubs-4, ubs-5, ubs-6, ubs-7, ubs-8, ubs-9 }

ZeroSizeBitString ::= BIT STRING (SIZE(0))
zsbs1 ZeroSizeBitString ::= ''B
zsbs2 ZeroSizeBitString ::= ''H

ZeroSizeBitStringList ::= SEQUENCE OF ZeroSizeBitString
zsbsl ZeroSizeBitStringList ::= { zsbs1, zsbs2 }

ConstBitString1 ::= BIT STRING ('1337'H)
cbs1 ConstBitString1 ::= '1337'H

ConstBitString2 ::= BIT STRING ('10101'B)
cbs2 ConstBitString2 ::= '10101'B

OneBitBitString ::= BIT STRING (SIZE(1))
obbs-1 OneBitBitString ::= '0'B
obbs-2 OneBitBitString ::= '1'B

OneBitBitStringList ::= SEQUENCE OF OneBitBitString
obbsl OneBitBitStringList ::= { obbs-1, obbs-2 }

SizeRangeBitString1 ::= BIT STRING (SIZE(0..4))
srbs1-1 SizeRangeBitString1 ::= ''B
srbs1-2 SizeRangeBitString1 ::= '1'B
srbs1-3 SizeRangeBitString1 ::= '10'B
srbs1-4 SizeRangeBitString1 ::= '101'B
srbs1-5 SizeRangeBitString1 ::= '1010'B
srbs1-6 SizeRangeBitString1 ::= 'A'H

SizeRangeBitString1List ::= SEQUENCE OF SizeRangeBitString1
srbs1l SizeRangeBitString1List ::= { srbs1-1, srbs1-2, srbs1-3, srbs1-4, srbs1-5, srbs1-6 }

SizeRangeBitString2 ::= BIT STRING (SIZE(2..4))
srbs2-1 SizeRangeBitString2 ::= '10'B
srbs2-2 SizeRangeBitString2 ::= '101'B
srbs2-3 SizeRangeBitString2 ::= '1010'B
srbs2-4 SizeRangeBitString2 ::= 'A'H

SizeRangeBitString2List ::= SEQUENCE OF SizeRangeBitString2
srbs2l SizeRangeBitString2List ::= { srbs2-1, srbs2-2, srbs2-3, srbs2-4 }

SizeRangeBitString3 ::= BIT STRING (SIZE(1..<3 | 5<..7))
srbs3-1 SizeRangeBitString3 ::= '1'B
srbs3-2 SizeRangeBitString3 ::= '10'B
srbs3-3 SizeRangeBitString3 ::= '101010'B
srbs3-4 SizeRangeBitString3 ::= '1010101'B

SizeRangeBitString3List ::= SEQUENCE OF SizeRangeBitString3
srbs3l SizeRangeBitString3List ::= { srbs3-1, srbs3-2, srbs3-3, srbs3-4 }

SizeMaxBitString1 ::= BIT STRING (SIZE(0..MAX))
smbs1-1 SizeMaxBitString1 ::= ''B
smbs1-2 SizeMaxBitString1 ::= '1010'B
smbs1-3 SizeMaxBitString1 ::= 'AABB'H

SizeMaxBitString1List ::= SEQUENCE OF SizeMaxBitString1
smbs1l SizeMaxBitString1List ::= { smbs1-1, smbs1-2, smbs1-3 }

SizeMaxBitString2 ::= BIT STRING (SIZE(2..MAX))
smbs2-1 SizeMaxBitString2 ::= '10'B
smbs2-2 SizeMaxBitString2 ::= '1010'B
smbs2-3 SizeMaxBitString2 ::= 'AABBCCDD'H

SizeMaxBitString2List ::= SEQUENCE OF SizeMaxBitString2
smbs2l SizeMaxBitString2List ::= { smbs2-1, smbs2-2, smbs2-3 }

ExtensibleZeroSizeBitString1 ::= BIT STRING (SIZE(0, ...))
ezsbs1 ExtensibleZeroSizeBitString1 ::= ''B

ExtensibleZeroSizeBitString2 ::= BIT STRING (SIZE(0), ...)
ezsbs2 ExtensibleZeroSizeBitString1 ::= ''B

ConstOrSizedBitString ::= BIT STRING('1010'B | SIZE(1))
cbsbs-1 ConstOrSizedBitString ::= '1010'B
cbsbs-2 ConstOrSizedBitString ::= '1'B

ConstOrSizedBitStringList ::= SEQUENCE OF ConstOrSizedBitString
cbsbsl ConstOrSizedBitStringList ::= { cbsbs-1, cbsbs-2 }

ExtensibleSizeRangeBitString1 ::= BIT STRING (SIZE(0..4, ...))
esrbs1-1 ExtensibleSizeRangeBitString1 ::= ''B
esrbs1-2 ExtensibleSizeRangeBitString1 ::= '1'B
esrbs1-3 ExtensibleSizeRangeBitString1 ::= '10'B
esrbs1-4 ExtensibleSizeRangeBitString1 ::= '101'B
esrbs1-5 ExtensibleSizeRangeBitString1 ::= '1010'B

ExtensibleSizeRangeBitString1List ::= SEQUENCE OF ExtensibleSizeRangeBitString1
esrbs1l ExtensibleSizeRangeBitString1List ::= { esrbs1-1, esrbs1-2, esrbs1-3, esrbs1-4, esrbs1-5 }

ExtensibleSizeRangeBitString2 ::= BIT STRING (SIZE(0..2, ..., 2<..4))
esrbs2-1 ExtensibleSizeRangeBitString2 ::= ''B
esrbs2-2 ExtensibleSizeRangeBitString2 ::= '1'B
esrbs2-3 ExtensibleSizeRangeBitString2 ::= '10'B
esrbs2-4 ExtensibleSizeRangeBitString2 ::= '101'B
esrbs2-5 ExtensibleSizeRangeBitString2 ::= '1010'B

ExtensibleSizeRangeBitString2List ::= SEQUENCE OF ExtensibleSizeRangeBitString2
esrbs2l ExtensibleSizeRangeBitString2List ::= { esrbs2-1, esrbs2-2, esrbs2-3, esrbs2-4, esrbs2-5 }

ExtensibleSizeRangeBitString3 ::= BIT STRING (SIZE(0..2), ..., SIZE(2<..4))
esrbs3-1 ExtensibleSizeRangeBitString3 ::= ''B
esrbs3-2 ExtensibleSizeRangeBitString3 ::= '1'B
esrbs3-3 ExtensibleSizeRangeBitString3 ::= '10'B
esrbs3-4 ExtensibleSizeRangeBitString3 ::= '101'B
esrbs3-5 ExtensibleSizeRangeBitString3 ::= '1010'B

ExtensibleSizeRangeBitString3List ::= SEQUENCE OF ExtensibleSizeRangeBitString3
esrbs3l ExtensibleSizeRangeBitString3List ::= { esrbs3-1, esrbs3-2, esrbs3-3, esrbs3-4, esrbs3-5 }

ExtensibleSizeRangeBitString4 ::= BIT STRING (SIZE(0..1, ..., 2), ..., SIZE(2<..4, ...) | SIZE(5))
esrbs4-1 ExtensibleSizeRangeBitString4 ::= ''B
esrbs4-2 ExtensibleSizeRangeBitString4 ::= '1'B
esrbs4-3 ExtensibleSizeRangeBitString4 ::= '10'B
esrbs4-4 ExtensibleSizeRangeBitString4 ::= '101'B
esrbs4-5 ExtensibleSizeRangeBitString4 ::= '1010'B
esrbs4-6 ExtensibleSizeRangeBitString4 ::= '10101'B

ExtensibleSizeRangeBitString4List ::= SEQUENCE OF ExtensibleSizeRangeBitString4
esrbs4l ExtensibleSizeRangeBitString4List ::= { esrbs4-1, esrbs4-2, esrbs4-3, esrbs4-4, esrbs4-5, esrbs4-6 }

ExtensibleSizeRangeBitString5 ::= BIT STRING (SIZE(0..1, ..., 2) | SIZE(3..4))
esrbs5-1 ExtensibleSizeRangeBitString5 ::= ''B
esrbs5-2 ExtensibleSizeRangeBitString5 ::= '1'B
esrbs5-3 ExtensibleSizeRangeBitString5 ::= '10'B
esrbs5-4 ExtensibleSizeRangeBitString5 ::= '101'B
esrbs5-5 ExtensibleSizeRangeBitString5 ::= '1010'B

ExtensibleSizeRangeBitString5List ::= SEQUENCE OF ExtensibleSizeRangeBitString5
esrbs5l ExtensibleSizeRangeBitString5List ::= { esrbs5-1, esrbs5-2, esrbs5-3, esrbs5-4, esrbs5-5 }

UnconstrainedNamedBitString ::= BIT STRING { a(0), b(1), c(2), d(7), e(8), f(255), g(256) }
unbs-empty UnconstrainedNamedBitString ::= {}
unbs-a UnconstrainedNamedBitString ::= { a }
unbs-b UnconstrainedNamedBitString ::= { b }
unbs-c UnconstrainedNamedBitString ::= { c }
unbs-d UnconstrainedNamedBitString ::= { d }
unbs-e UnconstrainedNamedBitString ::= { e }
unbs-f UnconstrainedNamedBitString ::= { f }
unbs-g UnconstrainedNamedBitString ::= { g }
unbs-ad UnconstrainedNamedBitString ::= { a, d }
unbs-ae UnconstrainedNamedBitString ::= { a, e }
unbs-all UnconstrainedNamedBitString ::= { a, b, c, d, e, f, g }

ConstNamedBitString ::= BIT STRING { foo(7) } ({ foo })
cnbs ConstNamedBitString ::= { foo }

OneBitNamedBitString ::= BIT STRING { a(0) } (SIZE(1))
obnbs OneBitNamedBitString ::= { a }

SizeRangeNamedBitString1 ::= BIT STRING { a(0), b(1), c(2), d(3) } (SIZE(0..4))
srnbs1-1 SizeRangeNamedBitString1 ::= { }
srnbs1-2 SizeRangeNamedBitString1 ::= { a }
srnbs1-3 SizeRangeNamedBitString1 ::= { b }
srnbs1-4 SizeRangeNamedBitString1 ::= { c }
srnbs1-5 SizeRangeNamedBitString1 ::= { d }
srnbs1-6 SizeRangeNamedBitString1 ::= { a, b, c, d }

SizeRangeNamedBitString1List ::= SEQUENCE OF SizeRangeNamedBitString1
srnbs1l SizeRangeNamedBitString1List ::= { srnbs1-1, srnbs1-2, srnbs1-3, srnbs1-4, srnbs1-5, srnbs1-6 }

SizeRangeNamedBitString2 ::= BIT STRING { a(0), b(1), c(2), d(3) } (SIZE(100..200))
srnbs2-1 SizeRangeNamedBitString2 ::= { }
srnbs2-2 SizeRangeNamedBitString2 ::= { a }
srnbs2-3 SizeRangeNamedBitString2 ::= { b }
srnbs2-4 SizeRangeNamedBitString2 ::= { c }
srnbs2-5 SizeRangeNamedBitString2 ::= { d }
srnbs2-6 SizeRangeNamedBitString2 ::= { a, b, c, d }

SizeRangeNamedBitString2List ::= SEQUENCE OF SizeRangeNamedBitString2
srnbs2l SizeRangeNamedBitString2List ::= { srnbs2-1, srnbs2-2, srnbs2-3, srnbs2-4, srnbs2-5, srnbs2-6 }

END
