TypeIdentifierTest DEFINITIONS IMPLICIT TAGS ::= BEGIN

REQUEST ::= TYPE-IDENTIFIER

id-request-hello-world OBJECT IDENTIFIER ::= { joint-iso-itu-t artasn(1337) test(47) request(0) hello-world(0) }
id-request-read-dir    OBJECT IDENTIFIER ::= { joint-iso-itu-t artasn(1337) test(47) request(0) read-dir(1)    }
id-request-read-file   OBJECT IDENTIFIER ::= { joint-iso-itu-t artasn(1337) test(47) request(0) read-file(2)   }

ReadDirRequest ::= SEQUENCE {
    directory            IA5String,
    include-hidden-files BOOLEAN
}

ReadFileRequest ::= SEQUENCE {
    file IA5String
}

helloWorldRequest REQUEST ::= { [PRIVATE 0] NULL IDENTIFIED BY id-request-hello-world }
readFileRequest   REQUEST ::= { ReadFileRequest  IDENTIFIED BY id-request-read-file   }

Requests REQUEST ::= {
    helloWorldRequest |
    { ReadDirRequest IDENTIFIED BY id-request-read-dir } |
    readFileRequest,
    ...
}

RequestData ::= SEQUENCE {
    num  [0] INTEGER,
    type [1] REQUEST.&id   ({Requests}),
    data [2] REQUEST.&Type ({Requests}{@type})
}

hello-world-request-1 RequestData ::= {
    num 100,
    type id-request-hello-world,
    data NULL : NULL
}
hello-world-request-2 RequestData ::= {
    num 101,
    type helloWorldRequest.&id,
    data helloWorldRequest.&Type : NULL
}
hello-world-request-3 RequestData ::= {
    num 102,
    type helloWorldRequest.&id,
    data NULL : NULL
}
hello-world-request-4 RequestData ::= {
    num 103,
    type id-request-hello-world,
    data helloWorldRequest.&Type : NULL
}

read-dir-request-1 RequestData ::= {
    num 200,
    type id-request-read-dir,
    data ReadDirRequest : {
        directory "/",
        include-hidden-files TRUE
    }
}

read-file-request-1 RequestData ::= {
    num 300,
    type id-request-read-file,
    data ReadFileRequest : {
        file "/foo.txt"
    }
}
read-file-request-2 RequestData ::= {
    num 301,
    type readFileRequest.&id,
    data readFileRequest.&Type : {
        file "/foo.txt"
    }
}
read-file-request-3 RequestData ::= {
    num 302,
    type readFileRequest.&id,
    data ReadFileRequest : {
        file "/foo.txt"
    }
}
read-file-request-4 RequestData ::= {
    num 303,
    type id-request-read-file,
    data readFileRequest.&Type : {
        file "/foo.txt"
    }
}

END
