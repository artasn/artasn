ContainedSubtypeConstraintTest DEFINITIONS IMPLICIT TAGS ::= BEGIN

WarningColor ::= UTF8String ("Red" | "Yellow")
wc-valid1 WarningColor ::= "Red"
wc-valid2 WarningColor ::= "Yellow"
wc-invalid1 WarningColor ::= "Blue"
wc-invalid2 WarningColor ::= "White"
wc-invalid3 WarningColor ::= "Purple"
wc-invalid4 WarningColor ::= ""

InfoColor ::= UTF8String ("Blue" | "White")
ic-valid1 InfoColor ::= "Blue"
ic-valid2 InfoColor ::= "White"
ic-invalid1 InfoColor ::= "Red"
ic-invalid2 InfoColor ::= "Yellow"
ic-invalid3 InfoColor ::= "Purple"
ic-invalid4 InfoColor ::= ""

WarningColorSubtype1 ::= UTF8String (WarningColor)
wcs1-valid1 WarningColorSubtype1 ::= "Red"
wcs1-valid2 WarningColorSubtype1 ::= "Yellow"
wcs1-invalid1 WarningColorSubtype1 ::= "Blue"
wcs1-invalid2 WarningColorSubtype1 ::= "White"
wcs1-invalid3 WarningColorSubtype1 ::= "Purple"
wcs1-invalid4 WarningColorSubtype1 ::= ""

WarningColorSubtype2 ::= UTF8String (INCLUDES WarningColor)
wcs2-valid1 WarningColorSubtype2 ::= "Red"
wcs2-valid2 WarningColorSubtype2 ::= "Yellow"
wcs2-invalid1 WarningColorSubtype2 ::= "Blue"
wcs2-invalid2 WarningColorSubtype2 ::= "White"
wcs2-invalid3 WarningColorSubtype2 ::= "Purple"
wcs2-invalid4 WarningColorSubtype2 ::= ""

WarningColorSubtype3 ::= UTF8String ([APPLICATION 4] WarningColor)
wcs3-valid1 WarningColorSubtype3 ::= "Red"
wcs3-valid2 WarningColorSubtype3 ::= "Yellow"
wcs3-invalid1 WarningColorSubtype3 ::= "Blue"
wcs3-invalid2 WarningColorSubtype3 ::= "White"
wcs3-invalid3 WarningColorSubtype3 ::= "Purple"
wcs3-invalid4 WarningColorSubtype3 ::= ""

WarningColorSubtype4 ::= UTF8String (INCLUDES [APPLICATION 4] WarningColor)
wcs4-valid1 WarningColorSubtype4 ::= "Red"
wcs4-valid2 WarningColorSubtype4 ::= "Yellow"
wcs4-invalid1 WarningColorSubtype4 ::= "Blue"
wcs4-invalid2 WarningColorSubtype4 ::= "White"
wcs4-invalid3 WarningColorSubtype4 ::= "Purple"
wcs4-invalid4 WarningColorSubtype4 ::= ""

ExtendedInfoColor ::= UTF8String ("Blue" | "White", ..., "Green")
xic-valid1 ExtendedInfoColor ::= "Blue"
xic-valid2 ExtendedInfoColor ::= "White"
xic-valid3 ExtendedInfoColor ::= "Green"
xic-invalid1 ExtendedInfoColor ::= "Red"
xic-invalid2 ExtendedInfoColor ::= "Yellow"
xic-invalid3 ExtendedInfoColor ::= "Purple"
xic-invalid4 ExtendedInfoColor ::= ""

ExtendedInfoColorSubtype ::= UTF8String (ExtendedInfoColor)
xics-valid1 ExtendedInfoColorSubtype ::= "Blue"
xics-valid2 ExtendedInfoColorSubtype ::= "White"
xics-invalid1 ExtendedInfoColorSubtype ::= "Red"
xics-invalid2 ExtendedInfoColorSubtype ::= "Yellow"
xics-invalid3 ExtendedInfoColorSubtype ::= "Purple"
xics-invalid4 ExtendedInfoColorSubtype ::= ""
xics-invalid5 ExtendedInfoColorSubtype ::= "Green"

SignColor1 ::= UTF8String (InfoColor | WarningColor)
sc1-valid1 SignColor1 ::= "Red"
sc1-valid2 SignColor1 ::= "Yellow"
sc1-valid3 SignColor1 ::= "Blue"
sc1-valid4 SignColor1 ::= "White"
sc1-invalid1 SignColor1 ::= "Purple"
sc1-invalid2 SignColor1 ::= ""

SignColor2 ::= UTF8String (InfoColor UNION WarningColor)
sc2-valid1 SignColor2 ::= "Red"
sc2-valid2 SignColor2 ::= "Yellow"
sc2-valid3 SignColor2 ::= "Blue"
sc2-valid4 SignColor2 ::= "White"
sc2-invalid1 SignColor2 ::= "Purple"
sc2-invalid2 SignColor2 ::= ""

SignColor3 ::= UTF8String (INCLUDES InfoColor | WarningColor)
sc3-valid1 SignColor3 ::= "Red"
sc3-valid2 SignColor3 ::= "Yellow"
sc3-valid3 SignColor3 ::= "Blue"
sc3-valid4 SignColor3 ::= "White"
sc3-invalid1 SignColor3 ::= "Purple"
sc3-invalid2 SignColor3 ::= ""

SignColor4 ::= UTF8String (InfoColor | INCLUDES WarningColor)
sc4-valid1 SignColor1 ::= "Red"
sc4-valid2 SignColor1 ::= "Yellow"
sc4-valid3 SignColor1 ::= "Blue"
sc4-valid4 SignColor1 ::= "White"
sc4-invalid1 SignColor1 ::= "Purple"
sc4-invalid2 SignColor1 ::= ""

SignColor5 ::= UTF8String (INCLUDES InfoColor | INCLUDES WarningColor)
sc5-valid1 SignColor4 ::= "Red"
sc5-valid2 SignColor4 ::= "Yellow"
sc5-valid3 SignColor4 ::= "Blue"
sc5-valid4 SignColor4 ::= "White"
sc5-invalid1 SignColor4 ::= "Purple"
sc5-invalid2 SignColor4 ::= ""

CitySpeedLimit ::= INTEGER (25 | 30 | 40)
csl-valid1 CitySpeedLimit ::= 25
csl-valid2 CitySpeedLimit ::= 30
csl-valid3 CitySpeedLimit ::= 40
csl-invalid1 CitySpeedLimit ::= 50
csl-invalid2 CitySpeedLimit ::= 60
csl-invalid3 CitySpeedLimit ::= 70
csl-invalid4 CitySpeedLimit ::= 1337
csl-invalid5 CitySpeedLimit ::= 0

HighwaySpeedLimit ::= INTEGER (40 | 50 | 60 | 70)
hsl-valid1 HighwaySpeedLimit ::= 40
hsl-valid2 HighwaySpeedLimit ::= 50
hsl-valid3 HighwaySpeedLimit ::= 60
hsl-valid4 HighwaySpeedLimit ::= 70
hsl-invalid1 HighwaySpeedLimit ::= 25
hsl-invalid2 HighwaySpeedLimit ::= 30
hsl-invalid3 HighwaySpeedLimit ::= 1337
hsl-invalid4 HighwaySpeedLimit ::= 0

SpeedLimit1 ::= INTEGER (CitySpeedLimit | HighwaySpeedLimit)
sl1-valid1 SpeedLimit1 ::= 25
sl1-valid2 SpeedLimit1 ::= 30
sl1-valid3 SpeedLimit1 ::= 40
sl1-valid4 SpeedLimit1 ::= 50
sl1-valid5 SpeedLimit1 ::= 60
sl1-valid6 SpeedLimit1 ::= 70
sl1-invalid1 SpeedLimit1 ::= 1337
sl1-invalid2 SpeedLimit1 ::= 0

SpeedLimit2 ::= INTEGER (CitySpeedLimit UNION HighwaySpeedLimit)
sl2-valid1 SpeedLimit2 ::= 25
sl2-valid2 SpeedLimit2 ::= 30
sl2-valid3 SpeedLimit2 ::= 40
sl2-valid4 SpeedLimit2 ::= 50
sl2-valid5 SpeedLimit2 ::= 60
sl2-valid6 SpeedLimit2 ::= 70
sl2-invalid1 SpeedLimit2 ::= 1337
sl2-invalid2 SpeedLimit2 ::= 0

RuralSpeedLimit1 ::= INTEGER (CitySpeedLimit ^ HighwaySpeedLimit)
rsl1-valid1 RuralSpeedLimit1 ::= 40
rsl1-invalid1 RuralSpeedLimit1 ::= 25
rsl1-invalid2 RuralSpeedLimit1 ::= 30
rsl1-invalid3 RuralSpeedLimit1 ::= 50
rsl1-invalid4 RuralSpeedLimit1 ::= 60
rsl1-invalid5 RuralSpeedLimit1 ::= 70
rsl1-invalid6 RuralSpeedLimit1 ::= 1337
rsl1-invalid7 RuralSpeedLimit1 ::= 0

RuralSpeedLimit2 ::= INTEGER (CitySpeedLimit INTERSECTION HighwaySpeedLimit)
rsl2-valid1 RuralSpeedLimit2 ::= 40
rsl2-invalid1 RuralSpeedLimit2 ::= 25
rsl2-invalid2 RuralSpeedLimit2 ::= 30
rsl2-invalid3 RuralSpeedLimit2 ::= 50
rsl2-invalid4 RuralSpeedLimit2 ::= 60
rsl2-invalid5 RuralSpeedLimit2 ::= 70
rsl2-invalid6 RuralSpeedLimit2 ::= 1337
rsl2-invalid7 RuralSpeedLimit2 ::= 0

IntA ::= INTEGER (1 | 2 | 3)
IntB ::= INTEGER (4 | 5 | 6)
IntC ::= INTEGER (1 | 6)

IntAuBiC1 ::= INTEGER (IntA | IntB ^ IntC)
aubic1-1 IntAuBiC1 ::= 1
aubic1-2 IntAuBiC1 ::= 2
aubic1-3 IntAuBiC1 ::= 3
aubic1-4 IntAuBiC1 ::= 4
aubic1-5 IntAuBiC1 ::= 5
aubic1-6 IntAuBiC1 ::= 6

IntAuBiC2 ::= INTEGER ((IntA | IntB) ^ IntC)
aubic2-1 IntAuBiC2 ::= 1
aubic2-2 IntAuBiC2 ::= 2
aubic2-3 IntAuBiC2 ::= 3
aubic2-4 IntAuBiC2 ::= 4
aubic2-5 IntAuBiC2 ::= 5
aubic2-6 IntAuBiC2 ::= 6

IntAuBiC3 ::= INTEGER (IntA | (IntB ^ IntC))
aubic3-1 IntAuBiC3 ::= 1
aubic3-2 IntAuBiC3 ::= 2
aubic3-3 IntAuBiC3 ::= 3
aubic3-4 IntAuBiC3 ::= 4
aubic3-5 IntAuBiC3 ::= 5
aubic3-6 IntAuBiC3 ::= 6

IntAiBuC1 ::= INTEGER (IntA ^ IntB | IntC)
aibuc1-1 IntAiBuC1 ::= 1
aibuc1-2 IntAiBuC1 ::= 2
aibuc1-3 IntAiBuC1 ::= 3
aibuc1-4 IntAiBuC1 ::= 4
aibuc1-5 IntAiBuC1 ::= 5
aibuc1-6 IntAiBuC1 ::= 6

IntAiBuC2 ::= INTEGER ((IntA ^ IntB) | IntC)
aibuc2-1 IntAiBuC2 ::= 1
aibuc2-2 IntAiBuC2 ::= 2
aibuc2-3 IntAiBuC2 ::= 3
aibuc2-4 IntAiBuC2 ::= 4
aibuc2-5 IntAiBuC2 ::= 5
aibuc2-6 IntAiBuC2 ::= 6

IntAiBuC3 ::= INTEGER (IntA ^ (IntB | IntC))
aibuc3-1 IntAiBuC3 ::= 1
aibuc3-2 IntAiBuC3 ::= 2
aibuc3-3 IntAiBuC3 ::= 3
aibuc3-4 IntAiBuC3 ::= 4
aibuc3-5 IntAiBuC3 ::= 5
aibuc3-6 IntAiBuC3 ::= 6

IntBiCuA1 ::= INTEGER (IntB | IntC ^ IntA)
bicua1-1 IntBiCuA1 ::= 1
bicua1-2 IntBiCuA1 ::= 2
bicua1-3 IntBiCuA1 ::= 3
bicua1-4 IntBiCuA1 ::= 4
bicua1-5 IntBiCuA1 ::= 5
bicua1-6 IntBiCuA1 ::= 6

IntBiCuA2 ::= INTEGER ((IntB | IntC) ^ IntA)
bicua2-1 IntBiCuA2 ::= 1
bicua2-2 IntBiCuA2 ::= 2
bicua2-3 IntBiCuA2 ::= 3
bicua2-4 IntBiCuA2 ::= 4
bicua2-5 IntBiCuA2 ::= 5
bicua2-6 IntBiCuA2 ::= 6

IntBiCuA3 ::= INTEGER (IntB | (IntC ^ IntA))
bicua3-1 IntBiCuA3 ::= 1
bicua3-2 IntBiCuA3 ::= 2
bicua3-3 IntBiCuA3 ::= 3
bicua3-4 IntBiCuA3 ::= 4
bicua3-5 IntBiCuA3 ::= 5
bicua3-6 IntBiCuA3 ::= 6

IntDerived1 ::= INTEGER (((IntA ^ IntB | IntC) | ((IntB | IntC) ^ IntA)) ^ IntB)
id1-1 IntDerived1 ::= 1
id1-2 IntDerived1 ::= 2
id1-3 IntDerived1 ::= 3
id1-4 IntDerived1 ::= 4
id1-5 IntDerived1 ::= 5
id1-6 IntDerived1 ::= 6

IntDerived2 ::= INTEGER ((IntAiBuC1 | IntBiCuA2) ^ IntB)
id2-1 IntDerived2 ::= 1
id2-2 IntDerived2 ::= 2
id2-3 IntDerived2 ::= 3
id2-4 IntDerived2 ::= 4
id2-5 IntDerived2 ::= 5
id2-6 IntDerived2 ::= 6

END
