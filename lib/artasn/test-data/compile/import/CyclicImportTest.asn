CyclicImportTest DEFINITIONS AUTOMATIC TAGS ::= BEGIN

IMPORTS IntermediateType, intermediateValue FROM CyclicImportTestIntermediate
    RemoteType, remoteValue FROM CyclicImportTestRemote;

MainType ::= UTF8String
mainValue MainType ::= "Hello, world!"

value SEQUENCE {
    main MainType,
    intermediate IntermediateType,
    remote RemoteType
} ::= {
    main mainValue,
    intermediate intermediateValue,
    remote remoteValue
}

END
