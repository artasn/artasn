ComponentReferenceTest DEFINITIONS AUTOMATIC TAGS ::= BEGIN

SIGNATURE-ALGORITHM ::= CLASS {
    &id   OBJECT IDENTIFIER UNIQUE,
    &name UTF8String,
    &Value
} WITH SYNTAX {
    IDENTIFIER &id
    NAME &name
    VALUE &Value
}

FooSigValue ::= SEQUENCE {
    a INTEGER,
    b INTEGER
}

algo-foo SIGNATURE-ALGORITHM ::= {
    IDENTIFIER { joint-iso-itu-t artasn(1337) test(47) sig-algo(0) foo(0) }
    NAME "foo"
    VALUE FooSigValue
}

BarSigValue ::= OCTET STRING (SIZE(8))

algo-bar SIGNATURE-ALGORITHM ::= {
    IDENTIFIER { joint-iso-itu-t artasn(1337) test(47) sig-algo(0) bar(1) }
    NAME "bar"
    VALUE BarSigValue
}

SignatureAlgorithms SIGNATURE-ALGORITHM ::= { algo-foo | algo-bar }

SignedData ::= SEQUENCE {
    data OCTET STRING,
    algorithm SEQUENCE {
        id   SIGNATURE-ALGORITHM.&id   ({SignatureAlgorithms}),
        name SIGNATURE-ALGORITHM.&name ({SignatureAlgorithms}{@.id})
    },
    -- TODO: make this OCTET STRING (CONTAINING SIGNATURE-ALGORTIHM.&VALUE (...))
    signature SIGNATURE-ALGORITHM.&Value ({SignatureAlgorithms}{@algorithm.id})
}

foo-signed-data SignedData ::= {
    data 'DEADBEEF'H,
    algorithm {
        id   algo-foo.&id,
        name algo-foo.&name
    },
    signature algo-foo.&Value : {
        a 1, b 2
    }
}

bar-signed-data SignedData ::= {
    data 'DEADBEEF'H,
    algorithm {
        id   algo-bar.&id,
        name algo-bar.&name
    },
    signature algo-bar.&Value : '0123456789ABCDEF'H
}

END
