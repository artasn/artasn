ObjectSetTest DEFINITIONS AUTOMATIC TAGS ::= BEGIN

MESSAGE ::= TYPE-IDENTIFIER

null-message MESSAGE ::= { NULL IDENTIFIED BY { joint-iso-itu-t artasn(1337) test(47) message(0) null(0) } }
integer-message MESSAGE ::= { INTEGER IDENTIFIED BY { joint-iso-itu-t artasn(1337) test(47) message(0) integer(1) } }
utf8-message MESSAGE ::= { UTF8String IDENTIFIED BY { joint-iso-itu-t artasn(1337) test(47) message(0) utf8(2) } }
bytes-message MESSAGE ::= { OCTET STRING IDENTIFIED BY { joint-iso-itu-t artasn(1337) test(47) message(0) bytes(3) } }

Set1 MESSAGE ::= { null-message | integer-message }
Set2-v1 MESSAGE ::= { Set1 | utf8-message | bytes-message }
Set2-v2 MESSAGE ::= { Set1, ..., utf8-message | bytes-message }

Message-v1 ::= SEQUENCE {
    id   MESSAGE.&id   ({Set2-v1}),
    data MESSAGE.&Type ({Set2-v1}{@id})
}
null-message-v1 Message-v1 ::= {
    id   null-message.&id,
    data null-message.&Type : NULL
}
integer-message-v1 Message-v1 ::= {
    id   integer-message.&id,
    data integer-message.&Type : 1337
}
utf8-message-v1 Message-v1 ::= {
    id   utf8-message.&id,
    data utf8-message.&Type : "Hello, world!"
}
bytes-message-v1 Message-v1 ::= {
    id   bytes-message.&id,
    data bytes-message.&Type : 'DEADBEEF'H
}

Message-v2 ::= SEQUENCE {
    id   MESSAGE.&id   ({Set2-v2}),
    data MESSAGE.&Type ({Set2-v2}{@id})
}
null-message-v2 Message-v2 ::= {
    id   null-message.&id,
    data null-message.&Type : NULL
}
integer-message-v2 Message-v2 ::= {
    id   integer-message.&id,
    data integer-message.&Type : 1337
}
utf8-message-v2 Message-v2 ::= {
    id   utf8-message.&id,
    data utf8-message.&Type : "Hello, world!"
}
bytes-message-v2 Message-v2 ::= {
    id   bytes-message.&id,
    data bytes-message.&Type : 'DEADBEEF'H
}

END
