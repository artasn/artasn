CharacterStringTest DEFINITIONS AUTOMATIC TAGS ::= BEGIN

CharacterString ::= CHARACTER STRING

with-syntaxes CharacterString ::= {
    identification syntaxes : {
        abstract { joint-iso-itu-t asn1chef(1337) test(47) abstract(0) },
        transfer { joint-iso-itu-t asn1chef(1337) test(47) transfer(1) }
    },
    string-value '1337'H
}

with-syntax CharacterString ::= {
    identification syntax : { joint-iso-itu-t asn1chef(1337) test(47) syntax(2) },
    string-value '1337'H
}

with-presentation-context-id CharacterString ::= {
    identification presentation-context-id : 9001,
    string-value '1337'H
}

with-context-negotiation CharacterString ::= {
    identification context-negotiation : {
        presentation-context-id 9001,
        transfer-syntax { joint-iso-itu-t asn1chef(1337) test(47) transfer(1) }
    },
    string-value '1337'H
}

with-transfer-syntax CharacterString ::= {
    identification transfer-syntax : { joint-iso-itu-t asn1chef(1337) test(47) transfer(1) },
    string-value '1337'H
}

with-fixed CharacterString ::= {
    identification fixed : NULL,
    string-value '1337'H
}

END
