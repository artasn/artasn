External-X680Test DEFINITIONS AUTOMATIC TAGS ::= BEGIN

External ::= EXTERNAL

with-syntax External ::= {
    identification syntax : { joint-iso-itu-t asn1chef(1337) test(47) syntax(2) },
    data-value '1337'H
}

with-presentation-context-id External ::= {
    identification presentation-context-id : 9001,
    data-value '1337'H
}

with-context-negotiation External ::= {
    identification context-negotiation : {
        presentation-context-id 9001,
        transfer-syntax { joint-iso-itu-t asn1chef(1337) test(47) transfer(1) }
    },
    data-value '1337'H
}

with-syntax-and-descriptor External ::= {
    identification syntax : { joint-iso-itu-t asn1chef(1337) test(47) syntax(2) },
    data-value-descriptor "with-syntax-and-descriptor",
    data-value '1337'H
}

with-presentation-context-id-and-descriptor External ::= {
    identification presentation-context-id : 9001,
    data-value-descriptor "with-presentation-context-id-and-descriptor",
    data-value '1337'H
}

with-context-negotiation-and-descriptor External ::= {
    identification context-negotiation : {
        presentation-context-id 9001,
        transfer-syntax { joint-iso-itu-t asn1chef(1337) test(47) transfer(1) }
    },
    data-value-descriptor "with-context-negotiation-and-descriptor",
    data-value '1337'H
}

END
