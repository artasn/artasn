ObjectFieldTest DEFINITIONS AUTOMATIC TAGS ::= BEGIN

ATTRIBUTE ::= CLASS {
    &parent ATTRIBUTE OPTIONAL,
    &id     OBJECT IDENTIFIER UNIQUE,
    &name   UTF8String
} WITH SYNTAX {
    [SUBTYPE OF &parent WITH]
    ID          &id
    WITH NAME   &name
}

id-root        OBJECT IDENTIFIER ::= { joint-iso-itu-t asn1chef(1337) test(47) attribute(100) }
id-subject     OBJECT IDENTIFIER ::= { id-root subject(0) }
id-common-name OBJECT IDENTIFIER ::= { id-subject common-name(0) }

attr-root        ATTRIBUTE ::= { ID id-root WITH NAME "root" }
attr-subject     ATTRIBUTE ::= { SUBTYPE OF attr-root WITH ID id-subject WITH NAME "subject" }
attr-common-name ATTRIBUTE ::= { SUBTYPE OF attr-subject WITH ID id-common-name WITH NAME "common-name" }

Attributes ATTRIBUTE ::= { attr-root | attr-subject | attr-common-name, ... }

Attribute ::= SEQUENCE {
    parent Attribute OPTIONAL,
    id     ATTRIBUTE.&id   ({Attributes}),
    name   ATTRIBUTE.&name ({Attributes}{@id})
}

common-name Attribute ::= {
    parent {
        parent {
            id   attr-root.&id,
            name attr-root.&name
        },
        id   attr-subject.&id,
        name attr-subject.&name
    },
    id   attr-common-name.&id,
    name attr-common-name.&name
}

END
