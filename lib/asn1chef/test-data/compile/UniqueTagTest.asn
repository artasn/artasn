UniqueTagTest DEFINITIONS IMPLICIT TAGS ::= BEGIN

Compliant1 ::= SEQUENCE {
    num INTEGER
}

Compliant2 ::= SEQUENCE {
    num INTEGER OPTIONAL
}

Compliant3 ::= SEQUENCE {
    num1 INTEGER,
    num2 INTEGER
}

Compliant4 ::= SEQUENCE {
    num1 INTEGER,
    num2 INTEGER OPTIONAL
}

Compliant5 ::= SEQUENCE {
    num1 INTEGER OPTIONAL,
    bytes OCTET STRING,
    num2 INTEGER OPTIONAL
}

Compliant6 ::= SEQUENCE {
    num INTEGER OPTIONAL,
    bytes OCTET STRING OPTIONAL
}

Compliant7 ::= SEQUENCE {
    num1 [0] INTEGER OPTIONAL,
    num2 [1] INTEGER
}

Compliant8 ::= SEQUENCE {
    num1 [0] INTEGER OPTIONAL,
    num2 [1] INTEGER OPTIONAL
}

Compliant9 ::= SET {
    num INTEGER
}

Compliant10 ::= SET {
    num INTEGER OPTIONAL
}

Compliant11 ::= SET {
    num1 [0] INTEGER,
    num2 [1] INTEGER
}

Noncompliant1 ::= SEQUENCE {
    num1 INTEGER OPTIONAL,
    num2 INTEGER
}

Noncompliant2 ::= SEQUENCE {
    num1 INTEGER OPTIONAL,
    num2 INTEGER OPTIONAL
}

Noncompliant3 ::= SEQUENCE {
    num1 INTEGER OPTIONAL,
    bytes OCTET STRING OPTIONAL,
    num2 INTEGER
}

Noncompliant4 ::= SET {
    num1 INTEGER,
    num2 INTEGER
}

Noncompliant5 ::= SET {
    num1 INTEGER,
    bytes OCTET STRING,
    num2 INTEGER
}

END
